(defun C:THBPT( / s)
  (setq s    nil)
  (while     (and (/= s "A") (/= s "P") (/= s "a") (/= s "p"))
     (setq s     (getstring "[请选择打印方式:全部打印(A)/手选图框(P)]:")) 
    (print)
  )
  (cond
    ((or (= s "A") (= s "a")) (C:LPPDF))
    ((or (= s "P") (= s "p")) (C:LPPPDF))
  )
  (princ)
)


;****************字符串去除特殊字符**************
(defun lgm_mtext2text(MTextString / regex s)
    (setq regex(vlax-create-object "Vbscript.RegExp")) ;引用正则表达式控件
    (vlax-put-property regex "IgnoreCase" 0) ;不忽略大小写
    (vlax-put-property regex "Global" 1) ;匹配方式，全文字匹配
    (setq s MTextString)
    (vlax-put-property regex "Pattern" "\\\\([^;]*);")
    (WHILE     (= :VLAX-TRUE (vlax-invoke-method  regex "TEST" s))
        (setq s    (vlax-invoke-method  regex "Replace" s ""))
    )
    (vlax-put-property regex "Pattern" "(\\\\L|\\\\O|\\\\l|\\\\o|\\\\~|\\\\P|\\\\p|\\n|\\r|\\t|\\\\)+")
    (WHILE     (= :VLAX-TRUE (vlax-invoke-method  regex "TEST" s))
        (setq s    (vlax-invoke-method  regex "Replace" s ""))
    )
      (vlax-put-property regex "Pattern" " ")
      (setq s (vlax-invoke-method  regex "Replace" s ""))
    
      (vlax-put-property regex "Pattern" "({|})")
      (setq s (vlax-invoke-method  regex "Replace" s ""))

      (vlax-put-property regex "Pattern" "\\/")
      (setq s (vlax-invoke-method  regex "Replace" s "、"))

      (vlax-release-object regex)
     s
)


;*******************两点距离************
(DEFUN lgm_DIM2(PT1 PT2)
  (SQRT (+ (lgm_X2 (- (CAR PT2) (CAR PT1))) (lgm_X2 (- (CADR PT2) (CADR PT1)))))
)
;*******************平方************
(DEFUN lgm_X2(X)
  (* X X)
)

;***************随机数*************
(defun lgm_random( / n3 n4)
 (setq n3 (rtos (* 1000000000 (getvar "Date")) 2 16))
 ;(setq n3 (substr n3 18 1) n3 (atoi n3))
 ;(setq n4 (rem (getvar "CPUTICKS") 10))
 ;(rem (+ n3 n4)
)

(DEFUN lgm_GETOBVALUE(ENT_N)    ;获取文字内容
      (VLA-GET-TEXTSTRING (VLAX-ENAME->VLA-OBJECT (SSNAME ENT_N 0)))
)

(DEFUN lgm_GETDXFVALUE(ENT_N COUT)    ;获取对象组码对应数据
      (CDR (ASSOC COUT (ENTGET ENT_N)))
)

(defun lgm_plottofile(paper_sc dir_1 pt1 pt2 plot_sc pdf_name layout_name / layout_ob)
    (SETQ layout_ob (VLA-ITEM (VLA-GET-LAYOUTS (VLA-GET-ACTIVEDOCUMENT (VLAX-GET-ACAD-OBJECT))) layout_name))
    (vla-RefreshPlotDeviceInfo     layout_ob)
    (SETQ LIST_PLOTSTYLE (mapcar 'strcase (vlax-safearray->list (vlax-variant-value (vla-GetPlotStyleTableNames (vla-get-ActiveLayout (vla-get-ActiveDocument (vlax-get-acad-object))))))))
    (SETQ LIST_PPlotDeviceNames (mapcar 'strcase (vlax-safearray->list (vlax-variant-value (vla-GetPlotDeviceNames (vla-get-ActiveLayout (vla-get-ActiveDocument (vlax-get-acad-object))))))))
    (VLA-SetLayoutsToPlot (VLA-GET-PLOT (VLA-GET-ACTIVEDOCUMENT (VLAX-GET-ACAD-OBJECT)))  (vlax-safearray-fill (VLAX-MAKE-safearray vlax-vbString '(0 . 0)) (LIST LAYOUT_NAME)))
    (setq point1 (vlax-make-safearray vlax-vbDouble '(0 . 1)))
    (setq point2 (vlax-make-safearray vlax-vbDouble '(0 . 1)))
    (vlax-safearray-fill point1 (LIST (CAR (TRANS PT1 1 2)) (CADR (TRANS PT1 1 2))))
    (vlax-safearray-fill point2 (LIST (CAR (TRANS PT2 1 2)) (CADR (TRANS PT2 1 2))))
    (COND
        ((/= (member  (strcase "DWG TO PDF 2010.pc3")     LIST_PPlotDeviceNames) NIL )    (vla-put-ConfigName        layout_ob    "DWG TO PDF 2010.pc3"))
        ((/= (member  (strcase "DWG TO PDF 2012.pc3")     LIST_PPlotDeviceNames) NIL )    (vla-put-ConfigName        layout_ob    "DWG TO PDF 2012.pc3"))
        ((/= (member  (strcase "DWG TO PDF 2019.pc3")     LIST_PPlotDeviceNames) NIL )    (vla-put-ConfigName        layout_ob    "DWG TO PDF 2019.pc3"))
        (T                                    (progn(princ "警告：检查cad是否正确配置公司标准虚拟打印机." )(exit)))
    )
    (vla-put-CanonicalMediaName layout_ob     paper_sc)
    (setq     last_plotstyle     (substr     (vla-get-StyleSheet    layout_ob)     1    2))
    (if    (or (= last_plotstyle "H-")     (= last_plotstyle "A-")    (= last_plotstyle "E-")        (= last_plotstyle "W-")    (= last_plotstyle "S-")) 
        (vla-put-StyleSheet        layout_ob            (vla-get-StyleSheet    layout_ob))
        (COND
            ((/= (member  (strcase "H-PLOTTER.ctb")     LIST_PLOTSTYLE) NIL )    (vla-put-StyleSheet        layout_ob    "H-PLOTTER.CTB"))
            ((/= (member  (strcase "A-PLOTTER.ctb")     LIST_PLOTSTYLE) NIL )    (vla-put-StyleSheet        layout_ob    "A-PLOTTER.CTB"))
            ((/= (member  (strcase "E-PLOTTER.ctb")     LIST_PLOTSTYLE) NIL )    (vla-put-StyleSheet        layout_ob    "E-PRINTER.CTB"))
            ((/= (member  (strcase "W-PLOTTER.ctb")     LIST_PLOTSTYLE) NIL )    (vla-put-StyleSheet        layout_ob    "W-PLOTTER.CTB"))
            ((/= (member  (strcase "S-PLOTTER.ctb")     LIST_PLOTSTYLE) NIL )    (vla-put-StyleSheet        layout_ob    "S-PLOTTER.CTB"))
            (T                                (progn(princ "警告：检查cad是否正确安装公司打印样式." )(exit)))
        )
    )
    (vla-SetWindowToPlot         layout_ob     point1 point2)
    (vla-put-PaperUnits         layout_ob     acMillimeters )
    (vla-put-PlotType        layout_ob     acWindow)
    (vla-put-CenterPlot        layout_ob    :vlax-true)
    (vla-put-PlotHidden        layout_ob     :vlax-false)
    (vla-put-PlotRotation        layout_ob     dir_1)
    (vla-put-PlotWithLineweights    layout_ob    :vlax-true)
    (vla-put-PlotWithPlotStyles    layout_ob    :vlax-true)
    (vla-SetCustomScale         layout_ob     1 plot_sc)    
    (vla-PlotToFile (vla-get-Plot (vla-get-ActiveDocument (vlax-get-acad-object))) pdf_name)
)

(DEFUN lgm_RO_POINT(ANG_12 PT1 PT2)    ;点旋转
  (SETQ ANG_LINE (ANGLE PT1 PT2))
  (POLAR PT1 (+ ANG_LINE ANG_12) (lgm_DIM2 PT1 PT2))
)


;***********获取所有布局空间名称***********
(DEFUN LGM_GET_LAYOUTS()
  (VLA-GET-LAYOUTS (VLA-GET-ACTIVEDOCUMENT (VLAX-GET-ACAD-OBJECT)))
)

(DEFUN LGM_GET_LAYOUTCOUNT()
  (VLA-GET-COUNT (LGM_GET_LAYOUTS))
)


(DEFUN LGM_GET_LAYOUTNAMES()
  (SETQ N         (LGM_GET_LAYOUTCOUNT)
      I          0
    LAYOUT_NAMES    NIL
  )
  (REPEAT N
    (SETQ LAYOUT_N (VLAX-INVOKE (LGM_GET_LAYOUTS) 'ITEM I))
    (SETQ LAYOUT_N (VLA-GET-NAME LAYOUT_N))
    (IF     (/= LAYOUT_N "Model")
        (IF     (NOT LAYOUT_NAMES)
              (SETQ LAYOUT_NAMES (LIST LAYOUT_N))
              (SETQ LAYOUT_NAMES (APPEND LAYOUT_NAMES (LIST LAYOUT_N)))
        )
    )
    (SETQ I (+ I 1))    
  )
 (SETQ LAYOUT_NAMES LAYOUT_NAMES)
)
;**************END**************


(DEFUN LPPDF_SUB(SS_NAME)
  (SETQ &STR_PAPER (LIST     (LIST "A0L2"      '(841 1635)    "UserDefinedMetric (860.00 x 1645.00毫米)")
                (LIST "A0L1"      '(841 1486)    "UserDefinedMetric (860.00 x 1496.00毫米)")
                (LIST "A0L"      '(841 1189)    "UserDefinedMetric (860.00 x 1200.00毫米)")                
                (LIST "A1L1"      '(594 1051)    "UserDefinedMetric (605.00 x 1060.00毫米)")
                (LIST "A1L2"      '(594 1261)    "UserDefinedMetric (605.00 x 1270.00毫米)")
                (LIST "A1L4"      '(594 1682)    "UserDefinedMetric (605.00 x 1695.00毫米)")                
                (LIST "A1L5"      '(594 1892)    "UserDefinedMetric (605.00 x 1902.00毫米)")
                (LIST "A1L"      '(594 841)    "UserDefinedMetric (605.00 x 860.00毫米)")                
                (LIST "A2L1"      '(420 743)    "UserDefinedMetric (430.00 x 753.00毫米)")
                (LIST "A2L2"      '(420 891)    "UserDefinedMetric (430.00 x 900.00毫米)")
                (LIST "A2L"      '(420 594)    "UserDefinedMetric (430.00 x 605.00毫米)")
                (LIST "A3L"      '(297 420)    "UserDefinedMetric (305.00 x 430.00毫米)")
                (LIST "A4L"      '(297 210)    "UserDefinedMetric (220.00 x 305.00毫米)")
                (LIST "目录"      '(297 210)    "UserDefinedMetric (220.00 x 305.00毫米)")
          )
  )
        (setq     ss_obj (ssadd)
            ss_obj (ssadd ss_name ss_obj))
          (command "zoom" "o" ss_obj "")
            (SETQ     ENT_N    SS_NAME
                D_VALUE (lgm_GETDXFVALUE ENT_N 2)
                PLOT_SC    (lgm_GETDXFVALUE ENT_N 41)
                ANGLE_V (- (lgm_GETDXFVALUE ENT_N 50) (angle '(0 0 0) (getvar "ucsxdir")))
                PT1    (TRANS (lgm_GETDXFVALUE ENT_N 10) 0 1)
                PT1     (LIST (CAR PT1) (CADR PT1))
                J    0
            ) 
            (COND 
                ((< ANGLE_V 0.05)                (SETQ dir_1 ac90degrees))
                ((AND (> ANGLE_V 3.13) (< ANGLE_V 3.15))    (SETQ dir_1 ac270degrees))
                ((AND (> ANGLE_V 1.5) (< ANGLE_V 1.65))    (SETQ dir_1 ac0degrees))
                ((AND (> ANGLE_V 4.65) (< ANGLE_V 4.8))        (SETQ dir_1 ac180degrees))
                (T    (PROGN (PRINC "\n警告：图框角度无法识别...") (exit)))
            )
              (COND
                ((WCMATCH D_VALUE "*目录*")
                        (SETQ J 13)
                          (SETQ PT2     (LIST
                                        (+ (CAR  PT1)     (* PLOT_SC (NTH 1 (NTH 1 (NTH J &STR_PAPER)))) )
                                    (+ (CADR PT1)     (* PLOT_SC (NTH 0 (NTH 1 (NTH J &STR_PAPER)))) )
                                )
                        )
                        (SETQ $BH     "H0001")
                        (SETQ $TZMC     "图纸目录")
                        (SETQ BIANHAO (+ BIANHAO 1))
                        (SETQ BH_1 (ITOA BIANHAO))
                        (SETQ pdf_name    (STRCAT SAVEPATH $BH "_" $TZMC "_" BH_1 ".pdf"))
                        (PRINC "\n正在打印图纸")
                        (PRINC (STRCAT $BH "_" $TZMC "_" BH_1 "...\n"))
                        (SETQ paper_sc (NTH 2 (NTH J &STR_PAPER)))
                        (lgm_plottofile paper_sc ac0degrees pt1 pt2 plot_sc pdf_name layout_name)
                )
                ((WCMATCH D_VALUE "*A3变更单")
                        (SETQ J 11)
                          (SETQ PT2     (LIST
                                        (+ (CAR  PT1)     (* PLOT_SC (NTH 1 (NTH 1 (NTH J &STR_PAPER)))) )
                                    (+ (CADR PT1)     (* PLOT_SC (NTH 0 (NTH 1 (NTH J &STR_PAPER)))) )
                                )
                        )
                        (SETQ PT3     (LIST
                                        (+ (CAR  PT1)     (* PLOT_SC 170.5) )
                                    (+ (CADR PT1)     (* PLOT_SC 283.5) )
                                )
                        )
                        (SETQ PT4     (LIST
                                        (+ (CAR  PT1)     (* PLOT_SC 204.5) )
                                    (+ (CADR PT1)     (* PLOT_SC 276.5) )
                                )
                        )
                        (SETQ PT3     (lgm_RO_POINT ANGLE_V PT1 PT3))
                        (SETQ PT4     (lgm_RO_POINT ANGLE_V PT1 PT4))
                        (SETQ TEXT_ENT    (SSGET "F" (LIST PT3 PT4) '((0 . "TEXT,MTEXT"))))
                        (IF (= TEXT_ENT NIL) 
                            (PROGN (PRINC "\n警告:图纸编号缺失,请注意修改.\n") (SETQ $BH (lgm_random)))
                            (SETQ $BH (lgm_mtext2text (lgm_GETOBVALUE TEXT_ENT)))
                        )
                        (SETQ $TZMC     "变更通知单")
                        (SETQ BIANHAO (+ BIANHAO 1))
                        (SETQ BH_1 (ITOA BIANHAO))
                        (SETQ pdf_name    (STRCAT SAVEPATH $BH "_" $TZMC ".pdf"))
                        (PRINC "\n正在打印图纸")
                        (SETQ paper_sc (NTH 2 (NTH J &STR_PAPER)))
                        (lgm_plottofile paper_sc ac90degrees pt1 pt2 plot_sc pdf_name layout_name)
                )
                ((WCMATCH D_VALUE "*A4PREV")
                        (SETQ J 12)
                        (SETQ PT2     (LIST
                                        (+ (CAR  PT1)     (* PLOT_SC (NTH 1 (NTH 1 (NTH J &STR_PAPER)))) )
                                    (+ (CADR PT1)     (* PLOT_SC (NTH 0 (NTH 1 (NTH J &STR_PAPER)))) )
                                )
                        )
                        (SETQ PT3     (LIST
                                        (+ (CAR  PT1)     (* PLOT_SC 170.5) )
                                    (+ (CADR PT1)     (* PLOT_SC 283.5) )
                                )
                        )
                        (SETQ PT4     (LIST
                                        (+ (CAR  PT1)     (* PLOT_SC 204.5) )
                                    (+ (CADR PT1)     (* PLOT_SC 276.5) )
                                )
                        )
                        (SETQ PT3     (lgm_RO_POINT ANGLE_V PT1 PT3))
                        (SETQ PT4     (lgm_RO_POINT ANGLE_V PT1 PT4))
                        (SETQ TEXT_ENT    (SSGET "F" (LIST PT3 PT4) '((0 . "TEXT,MTEXT"))))
                        (IF (= TEXT_ENT NIL) 
                            (PROGN (PRINC "\n警告:图纸编号缺失,请注意修改.\n") (SETQ $BH (lgm_random)))
                            (SETQ $BH (lgm_mtext2text (lgm_GETOBVALUE TEXT_ENT)))
                        )
                        (SETQ $TZMC     "变更通知单")
                        (SETQ BIANHAO (+ BIANHAO 1))
                        (SETQ BH_1 (ITOA BIANHAO))
                        (SETQ pdf_name    (STRCAT SAVEPATH $BH "_" $TZMC ".pdf"))
                        (PRINC "\n正在打印图纸")
                        (SETQ paper_sc (NTH 2 (NTH J &STR_PAPER)))
                        (lgm_plottofile paper_sc ac0degrees pt1 pt2 plot_sc pdf_name layout_name)
                )
                ((WCMATCH D_VALUE "*A3L")
                        (SETQ J 11)
                          (SETQ PT2     (LIST
                                        (+ (CAR  PT1)     (* PLOT_SC (NTH 1 (NTH 1 (NTH J &STR_PAPER)))) )
                                    (+ (CADR PT1)     (* PLOT_SC (NTH 0 (NTH 1 (NTH J &STR_PAPER)))) )
                                )
                        )
                        (SETQ PT3    (LIST
                                        (+ (CAR  PT1)     (* PLOT_SC 372) )
                                    (+ (CADR PT1)     (* PLOT_SC 33.5) )
                                )
                        )
                        (SETQ PT4    (LIST
                                        (+ (CAR  PT1)     (* PLOT_SC 414.5) )
                                    (+ (CADR PT1)     (* PLOT_SC 16.5) )
                                )
                        )
                        (SETQ PT5    (LIST
                                        (+ (CAR  PT1)     (* PLOT_SC 372) )
                                    (+ (CADR PT1)     (* PLOT_SC 10.5) )
                                )
                        )
                        (SETQ PT6    (LIST
                                        (+ (CAR  PT1)     (* PLOT_SC 414.5) )
                                    (+ (CADR PT1)     (* PLOT_SC 5.2) )
                                )
                        )
                        (SETQ PT2     (lgm_RO_POINT ANGLE_V PT1 PT2))
                        (SETQ PT3     (lgm_RO_POINT ANGLE_V PT1 PT3))
                        (SETQ PT4     (lgm_RO_POINT ANGLE_V PT1 PT4))
                        (SETQ PT5     (lgm_RO_POINT ANGLE_V PT1 PT5))
                        (SETQ PT6     (lgm_RO_POINT ANGLE_V PT1 PT6))
                        (SETQ TEXT_ENT    (SSGET "F" (LIST PT5 PT6) '((0 . "TEXT,MTEXT"))))
                        (IF (= TEXT_ENT NIL) 
                            (PROGN (PRINC "\n警告:图纸编号缺失,请注意修改.\n") (SETQ $BH (lgm_random)))
                            (SETQ $BH (lgm_mtext2text (lgm_GETOBVALUE TEXT_ENT)))
                        )
                        (SETQ TEXT_ENT    (SSGET "F" (LIST PT3 PT4) '((0 . "TEXT,MTEXT"))))
                        (IF (= TEXT_ENT NIL) 
                            (PROGN (PRINC "\n警告:图纸项目名称缺失,请注意修改.\n") (SETQ $TZMC "图纸名"))
                            (SETQ $TZMC (lgm_mtext2text (lgm_GETOBVALUE TEXT_ENT)))
                        )
                        (SETQ pdf_name    (STRCAT SAVEPATH $BH "_" $TZMC ".pdf"))
                        (PRINC "\n正在打印图纸")
                        (PRINC $BH)
                        (PRINC "...\n")
                        (SETQ paper_sc (NTH 2 (NTH J &STR_PAPER)))
                        (lgm_plottofile paper_sc dir_1 pt1 pt2 plot_sc pdf_name layout_name)
                )

                (T
                    (PROGN
                        (SETQ J 0)
                              (WHILE    (NOT (WCMATCH D_VaLUE (strcat "*" (NTH 0 (NTH J &STR_PAPER)) "*")))
                                (SETQ J (+ J 1))
                            );ENDWHILE
                        (SETQ PT2     (LIST
                                        (+ (CAR  PT1)     (* PLOT_SC (NTH 1 (NTH 1 (NTH J &STR_PAPER)))) )
                                    (+ (CADR PT1)     (* PLOT_SC (NTH 0 (NTH 1 (NTH J &STR_PAPER)))) )
                                )
                        )
                        (SETQ PT3    (LIST
                                        (+ (CAR  PT1)     (* PLOT_SC (- (NTH 1 (NTH 1 (NTH J &STR_PAPER))) 10)) )
                                    (+ (CADR PT1)     (* PLOT_SC 10)  )
                                )
                        )
                        (SETQ PT4    (LIST
                                        (- (CAR  PT3)     (* PLOT_SC 60) )
                                    (+ (CADR PT3)     (* PLOT_SC 6)  )
                                )
                        )
                        (SETQ PT5    (LIST
                                        (- (CAR  PT3)     (* PLOT_SC 0) )
                                    (+ (CADR PT3)     (* PLOT_SC 16)  )
                                )
                        )
                        (SETQ PT6    (LIST
                                        (- (CAR  PT5)     (* PLOT_SC 60) )
                                    (+ (CADR PT5)     (* PLOT_SC 24) )
                                )
                        )
                        (SETQ PT2     (lgm_RO_POINT ANGLE_V PT1 PT2))
                        (SETQ PT3     (lgm_RO_POINT ANGLE_V PT1 PT3))
                        (SETQ PT4     (lgm_RO_POINT ANGLE_V PT1 PT4))
                        (SETQ PT5     (lgm_RO_POINT ANGLE_V PT1 PT5))
                        (SETQ PT6     (lgm_RO_POINT ANGLE_V PT1 PT6))
                        (SETQ TEXT_ENT    (SSGET "F" (LIST PT4 PT3) '((0 . "TEXT,MTEXT"))))
                        (IF (= TEXT_ENT NIL) 
                            (PROGN (PRINC "\n警告:图纸编号缺失,请注意修改.\n") (SETQ $BH (lgm_random)))
                            (SETQ $BH (lgm_mtext2text (lgm_GETOBVALUE TEXT_ENT)))
                        )
                        (SETQ TEXT_ENT    (SSGET "F" (LIST PT6 PT5) '((0 . "TEXT,MTEXT"))))
                        (IF (= TEXT_ENT NIL) 
                            (PROGN (PRINC "\n警告:图纸项目名称缺失,请注意修改.\n") (SETQ $TZMC "图纸名"))
                            (SETQ $TZMC (lgm_mtext2text (lgm_GETOBVALUE TEXT_ENT)))
                        )
                        (SETQ pdf_name    (STRCAT SAVEPATH $BH "_" $TZMC ".pdf"))
                        (PRINC "\n正在打印图纸")
                        (PRINC $BH)
                        (PRINC "...\n")
                        (SETQ paper_sc (NTH 2 (NTH J &STR_PAPER)))
                        (lgm_plottofile paper_sc dir_1 pt1 pt2 plot_sc pdf_name layout_name)          
                    );ENDPROGN
                )
              
            );ENDCOND
    
)


(DEFUN C:LPPDF()
  (defun *error*(msg)
      (SETVAR "OSMODE" #OS)
      (SETVAR "BACKGROUNDPLOT" #BGP)    
    (princ "error: ")
    (princ msg)
    (princ)
  )
  (vl-load-com)
 (COMMAND "UCS" "")
  (IF (= (SSGET "X" '((2 . "*_THAPE_*,*目录*")))  NIL)
    (PROGN 
        (PRINC "\n未检测到图纸,请检查是否为标准图框.")
      (EXIT)        
    )
  )
  (SETQ SAVWPATH NIL)
  (SETQ SAVEPATH    (lgm_GETPATH nil nil))
  (IF (= SAVEPATH NILE)
    (PROGN 
        (PRINC "\n★★★零人※制作.打印取消.★★★")
        (EXIT)
    )
  )
  (IF (= (SSGET "X" '((2 . "*_THAPE_*,*目录*") (410 . "Model")))  NIL)
    (SETQ &STR_MP "PAPER")
    (SETQ &STR_MP "MODEL")
  )
  (SETQ #BGP       (GETVAR "BACKGROUNDPLOT"))
  (SETQ #OS     (GETVAR "OSMODE"))
  (SETVAR "BACKGROUNDPLOT" 0)
  (SETVAR "OSMODE" 0)
  (setq bianhao 0)
  (IF (= &STR_MP "MODEL")
    (PROGN
        (SETQ layout_name "Model")
          (COMMAND "LAYOUT" "S" "Model")
          (SETQ SS_TUKUANG NIL)
        (SETQ     SS_TUKUANG    (SSGET "X" '((2 . "*_THAPE_*,*目录*") (410 . "Model"))))
        (setq i 0)
        (while (ssname ss_tukuang i)
            (lppdf_sub (ssname ss_tukuang i))
            (setq i (1+ i))
        )
          
    );ENDPROGN
  );ENDIF
  
            (SETQ LAYOUT_NAMES     (LGM_GET_LAYOUTNAMES))
            (SETQ M            (LENGTH LAYOUT_NAMES))
            (SETQ K 0)
            (REPEAT M
              (SETQ SS_TUKUANG NIL)
              (SETQ LAYOUT_NAME (NTH K LAYOUT_NAMES))
              (SETQ SS_TUKUANG    (SSGET "X" (LIST (CONS 2 "*_THAPE_*,*目录*") (CONS 410 LAYOUT_NAME))))
            (IF (NOT (NOT SS_TUKUANG))
                  (PROGN
                    (COMMAND "LAYOUT" "S" LAYOUT_NAME)
                      (setq i 0)
                    (while (ssname ss_tukuang i)
                        (lppdf_sub (ssname ss_tukuang i))
                        (setq i (1+ i))
                    )
                );ENDPROGN
            )
          (SETQ K (+ K 1))
        );ENDREPEAT
  (COMMAND "LAYOUT" "S" "Model")
  (SETVAR "OSMODE" #OS)
  (SETVAR "BACKGROUNDPLOT" #BGP)
  (vlax-invoke (vlax-create-object "Shell.Application") 'open SAVEPATH)
  (PRINC "\n★★★零人※制作.打印已完成.★★★")
  (princ)
)


(DEFUN C:LPPPDF()
  (defun *error*(msg)
      (SETVAR "OSMODE" #OS)
      (SETVAR "BACKGROUNDPLOT" #BGP)    
    (princ "error: ")
    (princ msg)
    (princ)
  )
  (vl-load-com)
  (COMMAND "UCS" "")
  (SETQ SS_TUKUANG NIL)
  (PRINC "\n请拾取需要打印的图框:")
  (SETQ     SS_TUKUANG    (SSGET '((2 . "*_THAPE_*,*目录*"))))
  (SETQ SAVEPATH NIL)
  (SETQ SAVEPATH    (lgm_GETPATH nil nil))
  (IF (= SAVEPATH NIL)
    (PROGN 
        (PRINC "\n★★★零人※制作.打印取消.★★★")
        (EXIT)
    )
  )
  (SETQ #BGP       (GETVAR "BACKGROUNDPLOT"))
  (SETQ #OS     (GETVAR "OSMODE"))
  (SETVAR "BACKGROUNDPLOT" 0)
  (SETVAR "OSMODE" 0)
  (setq bianhao 0)
    
            (IF (NOT (NOT SS_TUKUANG))
                  (PROGN
                    (SETQ     ENT_N    (SSNAME SS_TUKUANG 0))
                    (SETQ     LAYOUT_NAME    (lgm_GETDXFVALUE ENT_N 410))
                      (setq i 0)
                    (while (ssname ss_tukuang i)
                        (lppdf_sub (ssname ss_tukuang i))
                        (setq i (1+ i))
                    )
                );ENDPROGN
            )
  (SETVAR "OSMODE" #OS)
  (SETVAR "BACKGROUNDPLOT" #BGP)
  (vlax-invoke (vlax-create-object "Shell.Application") 'open SAVEPATH)
  (PRINC "\n★★★零人※制作.打印已完成.★★★")
  (princ)
)
